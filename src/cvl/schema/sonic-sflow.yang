module sonic-sflow {
        namespace "http://github.com/Azure/sonic-sflow";
        prefix sflow;

	import ietf-yang-types {
		prefix yang;
	}

	import ietf-inet-types {
		prefix inet;
	}

	import sonic-common {
		prefix scommon;
	}

        revision 2019-09-09 {
                description
                        "Initial revision.";
        }

        container sonic-sflow {
                list SFLOW_COLLECTOR {
                    max-elements 3;
                    key "collector_name";

                    leaf collector_name {
                        type string;
                    }

                    leaf collector_ip {
                        type enumeration {
                            enum inet:ipv4-address;
                            enum inet:ipv6-address;
                        }
                    }

                    leaf collector_port {
                        type inet:port-number;
                    }

                }

                list SFLOW_SESSION {
                    key "ifname";

                    leaf ifname {
                        type string;
                    }

                    leaf admin_state {
                        type scommon:admin-status;
                    }

                    leaf sample_rate {
                        type uint32;
                    }
                }

                container SFLOW {
                    container global {
                        leaf admin_state {
                            type scommon:admin-status;
                        }

                        leaf polling_interval {
                            type uint32;
                        }

                        leaf agent_id {
                            type string;
                        }
                    }
                }
        }
}
