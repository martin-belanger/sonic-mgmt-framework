module sonic-config-mgmt-annot {

    yang-version "1.1";

    namespace "http://openconfig.net/yang/annotation/cmgmt-annot";
    prefix "cmgmt-annot"; 

    import sonic-extensions { prefix sonic-ext; }
    import sonic-config-mgmt { prefix cmgmt; }

    deviation /cmgmt:config_save  {
      deviate add {
		sonic-ext:rpc-callback "rpc_config_save";
      }
    }
    deviation /cmgmt:config_reload  {
      deviate add {
		sonic-ext:rpc-callback "rpc_config_reload";
      }
    }
    deviation /cmgmt:config_load  {
      deviate add {
		sonic-ext:rpc-callback "rpc_config_load";
      }
    }
}
