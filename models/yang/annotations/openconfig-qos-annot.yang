module openconfig-qos-annot {

    yang-version "1.1";

    namespace "http://openconfig.net/yang/qos-annot";
    prefix "oc-qos-annot"; 

    import sonic-extensions { prefix sonic-ext; }
    import openconfig-qos { prefix oc-qos; }

    deviation /oc-qos:qos/oc-qos:interfaces {
      deviate add {
        sonic-ext:subtree-transformer "qos_get_all_intf_all_q_counters_xfmr";
        sonic-ext:db-name "COUNTERS_DB";
      }
    }

    deviation /oc-qos:qos/oc-qos:interfaces/oc-qos:interface/oc-qos:output/oc-qos:queues {
      deviate add {
        sonic-ext:subtree-transformer "qos_get_one_intf_all_q_counters_xfmr";
        sonic-ext:db-name "COUNTERS_DB";
      }
    }

    deviation /oc-qos:qos/oc-qos:interfaces/oc-qos:interface/oc-qos:output/oc-qos:queues/oc-qos:queue/oc-qos:state {
      deviate add {
        sonic-ext:subtree-transformer "qos_get_one_intf_one_q_counters_xfmr";
        sonic-ext:db-name "COUNTERS_DB";
      }
    }

}
