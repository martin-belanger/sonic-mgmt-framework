module dell-intf-augments {

  yang-version "1";

  namespace "http://openconfig.net/yang/interfaces/aggregate";
  
  prefix "if-agmnt";

  import openconfig-interfaces { prefix oc-if; }
  import openconfig-if-aggregate { prefix oc-lag; }

  // meta
  organization "OpenConfig working group";

  contact
    "OpenConfig working group
    netopenconfig@googlegroups.com";

  description
    "Model for managing aggregated (aka bundle, LAG) interfaces.";
     
  revision 2019-10-03 {
    description
      "Initial augment file.";
  }

  // augment statements

  augment "/oc-if:interfaces/oc-if:interface/oc-lag:aggregation/oc-lag:config" {
    leaf fallback {
      type boolean;
      description "Indicating whether lacp fallback is enabled or not";
    }
  }
  augment "/oc-if:interfaces/oc-if:interface/oc-lag:aggregation/oc-lag:state" {
    leaf fallback {
      type boolean;
      description "Fallback status on this interface";
    }
  }

}
