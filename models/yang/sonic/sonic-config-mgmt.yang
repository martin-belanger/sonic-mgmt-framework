module sonic-config-mgmt {
  namespace "http://github.com/Azure/sonic-config-mgmt";
  prefix scm;

  organization
    "BRCM";
  contact
    "BRCM";
  description
    "SONIC ERROR";

  revision 2019-09-15 {
    description
      "Initial revision.";
  }


  rpc copy {
      input {
          leaf source {
              type string;
          }

          leaf overwrite {
              type boolean;
          }

          leaf destination {
              type string;
          }
      }

      output {
          leaf status {
            type string;
            }
      }
  }
}
